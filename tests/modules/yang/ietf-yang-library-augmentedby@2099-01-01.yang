module ietf-yang-library-augmentedby {
  yang-version 1.1;
  namespace "urn:ietf:params:xml:ns:yang:ietf-yang-library-augmentedby";
  prefix yanglib-aug;

  import ietf-yang-library {
    prefix yanglib;
  }

  description
    "Test revision of ietf-yang-library-augmentedby differing from the built-in one.";

  revision 2099-01-01;
  revision 2025-05-28;

  grouping augmented-by {
    leaf-list augmented-by {
      type leafref {
        path "../../yanglib:module/yanglib:name";
      }
    }
  }

  augment "/yanglib:yang-library/yanglib:module-set/yanglib:module" {
    uses augmented-by;
  }

  augment "/yanglib:modules-state/yanglib:module" {
    status deprecated;
    uses augmented-by;
  }
}
